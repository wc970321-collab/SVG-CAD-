;; ==========================================
;; 玫瑰花实时手绘动态绘制插件 (AutoLISP)
;; 使用方法：复制全部代码粘贴到 CAD 命令行，或使用 APPLOAD 命令加载
;; ==========================================

(vl-load-com)
(defun c:roseanimate ( / draw-pline acad-obj doc)
  (setq acad-obj (vlax-get-acad-object))
  (setq doc (vla-get-ActiveDocument acad-obj))
  
  ;; 核心绘制函数：每画一笔，强制屏幕重画并延迟
  (defun draw-pline (pts / last-pt)
    (setq last-pt nil)
    (foreach pt pts
      (if last-pt
        (progn
          ;; 绘制一小段线段
          (command "_pline" last-pt pt "")
          ;; 强制更新CAD应用程序窗口，实现实时显示
          (vla-update acad-obj)
          ;; 每一笔的延迟时间（单位：毫秒）。"30" 代表 0.03 秒。
          (command "'delay" "30")
        )
      )
      (setq last-pt pt)
    )
  )

  (setvar "CMDECHO" 0) ; 关闭繁琐的命令行后台输出，让画面更干净
  
  ;; 1. 绘制最外层大花瓣
  (draw-pline '((0 120) (25 115) (50 100) (70 75) (80 45) (82 15) (75 -15) (60 -45) (40 -70) (15 -85) (0 -90) (-15 -85) (-40 -70) (-60 -45) (-75 -15) (-82 15) (-80 45) (-70 75) (-50 100) (-25 115) (0 120)))
  
  ;; 2. 绘制第二层交错花瓣
  (draw-pline '((0 90) (20 85) (38 70) (48 45) (48 15) (38 -15) (20 -40) (0 -50) (-20 -40) (-38 -15) (-48 15) (-48 45) (-38 70) (-20 85) (0 90)))

  ;; 3. 绘制第三层内花瓣
  (draw-pline '((0 60) (12 55) (22 42) (25 25) (20 5) (10 -15) (0 -20) (-10 -15) (-20 5) (-25 25) (-22 42) (-12 55) (0 60)))

  ;; 4. 绘制中心花芯
  (draw-pline '((0 30) (5 27) (8 18) (5 8) (0 5) (-5 8) (-8 18) (-5 27) (0 30)))

  ;; 5. 绘制向下弯曲的花茎
  (draw-pline '((0 -90) (3 -110) (12 -135) (15 -160) (12 -190) (5 -220) (0 -250)))

  ;; 6. 绘制花茎上的三颗尖刺
  (draw-pline '((15 -160) (25 -165) (13 -172)))
  (draw-pline '((12 -190) (22 -195) (10 -202)))
  (draw-pline '((-12 -190) (-22 -195) (-10 -202)))

  ;; 7. 绘制右侧大叶子
  (draw-pline '((12 -135) (32 -120) (48 -115) (60 -122) (65 -135) (60 -150) (48 -160) (30 -155) (15 -148)))
  ;; 绘制右侧叶脉
  (draw-pline '((32 -120) (40 -135) (48 -145)))
  (draw-pline '((48 -115) (44 -130) (42 -140)))
  (draw-pline '((60 -122) (52 -135)))

  ;; 8. 绘制左侧大叶子
  (draw-pline '((-3 -110) (-15 -100) (-30 -95) (-45 -100) (-52 -115) (-48 -130) (-35 -140) (-20 -138) (-8 -125)))
  ;; 绘制左侧叶脉
  (draw-pline '((-15 -100) (-25 -115) (-35 -125)))
  (draw-pline '((-30 -95) (-32 -112) (-35 -122)))
  (draw-pline '((-45 -100) (-38 -115)))

  (setvar "CMDECHO" 1)
  (command "_zoom" "_e")
  (princ "\n绘制已完成！")
  (princ)
)
(c:roseanimate)
